module ipv6 {
  namespace "http://example.com/ipv6";
  prefix ipv6;

  import tailf-common {
    prefix tailf;
  }
  import input_output {
    prefix input_output;
  }
  
   grouping ipv6 {
    container IPv6 {
      tailf:info "IPv6 related audits";
      // Configlet # 1
      container igmp {
        tailf:info "audit to check that ip igmp v3 set on VLAN 10 and gi0/0/0.10";
        uses input_output:input_output;
        }
      // Configlet # 2
    //  container L3_ip_pim {
      //  uses input_output:input_output;
      //  }
      }

    }
  }
