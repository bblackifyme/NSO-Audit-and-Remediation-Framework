// DO NOT MODIFY THIS FILE

module input_output {
  namespace "http://example.com/input_output";
  prefix input_output;

  import tailf-common {
    prefix tailf;
  }
  import tailf-ncs {
    prefix ncs;
  }

  grouping input_output {
  tailf:action audit {
    tailf:actionpoint audit;
    tailf:info "Input type can be 'device_group', 'device' or 'csv'";

    // DO NOT CHANGE THE INPUTS AND OUTPUTS
    input {
      list inputs {

        leaf input_type {
          type enumeration {
            enum "device_group";
            enum "device";
            enum "csv";
          }
        }

        leaf value {
          type string;
        }
      }
    }

    output {
      leaf username {
        type string;
      }
      leaf start_time {
        type string;
        mandatory true;
      }
      leaf end_time {
        type string;
        mandatory true;
      }
      leaf run_time {
        type string;
        mandatory true;
      }
      leaf number_audited {
        type int64;
      }

      list results {
        key "device";

        leaf device {
          type string;
        }
        leaf result {
          type boolean;
        }

      }
      leaf success_percent {
        type string;
      }
    }
  }
  // DO NOT CHANGE THE ACTION NAMES OR INPUTS & OUTPUTS
  tailf:action remediate {
    tailf:actionpoint audit;
    tailf:info "Remediation, Input type can be 'device_group', 'device' or 'csv'";
    input {
      list inputs {
        tailf:info "Input values for the action";

        leaf input_type {
          type enumeration {
            enum "device_group";
            enum "device";
            enum "csv";
          }
        }

        leaf value {
          type string;
        }
      }
    }

    output {
      leaf username {
        type string;
      }
      leaf start_time {
        type string;
        mandatory true;
      }
      leaf end_time {
        type string;
        mandatory true;
      }
      leaf run_time {
        type string;
        mandatory true;
      }
      leaf number_audited {
        type int64;
      }

      list results {
        key "device";

        leaf device {
          type string;
        }
        leaf result {
          type boolean;
        }

      }
      leaf success_percent {
        type string;
      }
    }
   }
 }
}
