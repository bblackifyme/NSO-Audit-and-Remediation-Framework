module your_audit_name_here { // Change this to your audits name, this needs to be the same everywhere
  namespace "http://example.com/your_audit_name_here"; // Change "your_audit_name_here" to your audits name, this needs to be the same everywhere
  prefix your_audit_name_here; // Change this to your audits name, this needs to be the same everywhere

  import tailf-common {
    prefix tailf;
  }
  import input_output {
    prefix input_output;
  }


  grouping your_audit_name_here {
    container your_audit_name_here { // Change this to your audits name, this needs to be the same everywhere
      tailf:info "Add description here";
      container your_sub_module_name_here { // Change this to your sub-use-cases name copy this for each new use case
        tailf:info "Add description here";
        uses input_output:input_output;
      }
      container your_sub_module_2_name_here { // Change this to your second sub-use-cases name copy this for each new use case
        tailf:info "Add description here";
        uses input_output:input_output;
      }

      }
    }
  }
