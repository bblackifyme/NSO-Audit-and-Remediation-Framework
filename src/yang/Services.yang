module Services { // Change this to your audits name, this needs to be the same everywhere
  namespace "http://example.com/your_audit_name_here"; // Change "your_audit_name_here" to your audits name, this needs to be the same everywhere
  prefix Services; // Change this to your audits name, this needs to be the same everywhere

  import tailf-common {
    prefix tailf;
  }
  import input_output {
    prefix input_output;
  }
  grouping Services { // Change this to your audits name, this needs to be the same everywhere
    container Services { // Change this to your audits name, this needs to be the same everywhere
      tailf:info "Add description here";
      container service_instances { // Change this to your sub-use-cases name copy this for each new use case
        tailf:info "Add description here";
        tailf:action audit {
          tailf:actionpoint audit;
          tailf:info "Audit";

          // DO NOT CHANGE THE INPUTS AND OUTPUTS
          input {

            leaf input_type {
              type enumeration{
                enum "All";
                enum "Specific";
              }
            }


            list inputs {
              when ../input_type="Specific";
              tailf:info "Input values for the action";

              leaf service {
                type string;
              }

              leaf instance {
                type string;
              }
            }
          }

          output {
            leaf username {
              type string;
            }
            leaf start_time {
              type string;
              mandatory true;
            }
            leaf end_time {
              type string;
              mandatory true;
            }
            leaf run_time {
              type string;
              mandatory true;
            }
            leaf number_audited {
              type int64;
            }

            list results {
              key "instance";

              leaf instance {
                type string;
              }
              leaf result {
                type boolean;
              }

            }
            leaf success_percent {
              type string;
            }
          }
        }
        // DO NOT CHANGE THE ACTION NAMES OR INPUTS & OUTPUTS
        tailf:action remediate {
          tailf:actionpoint audit;
          tailf:info "Remediation for the use case.";
          input {
            leaf Device_group {
              type string;
              mandatory true;
              tailf:info "NSO Device Group";
            }
          }

          output {
            leaf start_time {
              type string;
              mandatory true;
            }
            leaf end_time {
              type string;
              mandatory true;
            }
            leaf run_time {
              type string;
              mandatory true;
            }
            leaf number_audited {
              type int64;
            }

            list results {
              key device;
              leaf device {
                type string;
              }
              leaf result {
                type string;
              }
            }
            leaf success_percent {
              type string;
            }
          }
         }
      }

      }
    }
  }
